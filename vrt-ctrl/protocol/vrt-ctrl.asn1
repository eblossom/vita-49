--  -*- asn1-mode -*-
--
--  Copyright 2010 Free Software Foundation, Inc.
-- 
--  This program is free software: you can redistribute it and/or modify
--  it under the terms of the GNU General Public License as published by
--  the Free Software Foundation, either version 3 of the License, or
--  (at your option) any later version.
-- 
--  This program is distributed in the hope that it will be useful,
--  but WITHOUT ANY WARRANTY; without even the implied warranty of
--  MERCHANTABILITY or FITNESS FOR A PARTICULAR PURPOSE.  See the
--  GNU General Public License for more details.
-- 
--  You should have received a copy of the GNU General Public License
--  along with this program.  If not, see <http://www.gnu.org/licenses/>.
-- 

VRT-Control-Protocol { iso org(3) dod(6) internet(1) private(4) enterprise(1)
		       gnu(11591) radio(7) protocol(0) vrt-ctrl(0) rev(0) }
DEFINITIONS
AUTOMATIC TAGS ::=
BEGIN


-- VRT 64-bit 2's comp fixed point representation with radix point to the
-- right of bit 20 in the second 32-bit word.  Breaking it into two words
-- allows a compiler to avoid use of extended precision integers.

Vrt-hertz ::= SEQUENCE { 
  msw INTEGER, 					  -- most significant word
  lsw INTEGER 					  -- least significant word
}

--
-- 32-bit integer containing two 16-bit fixed point gains (VRT Figure 7.1.5.10-1)
-- In each stage, there are 7 bits to the right of the radix point.
--
--  3                     2                   1
--  1 0 9 8 7 6 5 4 3 2 1 0 9 8 7 6 5 4 3 2 1 0 9 8 7 6 5 4 3 2 1 0
-- +-+-+-+-+-+-+-+-+-+-+-+-+-+-+-+-+-+-+-+-+-+-+-+-+-+-+-+-+-+-+-+-+
-- |         Stage 2 Gain          |           Stage 1 Gain        |
-- +-+-+-+-+-+-+-+-+-+-+-+-+-+-+-+-+-+-+-+-+-+-+-+-+-+-+-+-+-+-+-+-+
--

Vrt-gain ::= INTEGER

Vrt-any ::= CHOICE {
  seq	        SEQUENCE OF Vrt-any,
  int		INTEGER,
  str		IA5String,
  octet-string	OCTET STRING
  --hertz		Vrt-hertz,
  --gain		Vrt-gain
}

Name ::= IA5String
Value ::= Vrt-any
Invocation-ID ::= INTEGER

Error-info ::= SEQUENCE {
  error-code	INTEGER,			  -- FIXME enum
  error-arg	Value
}

-- Commands

Get-args ::= SEQUENCE {
  name		Name
}

Get-meta-args ::= SEQUENCE {
  name		Name
}

Set-args ::= SEQUENCE {
  name		Name,
  value		Value
}

-- Operations

Call-op ::= SEQUENCE {
  inv-id	Invocation-ID,
  cmd	CHOICE {
    get-cmd	 Get-args,
    get-meta-cmd Get-meta-args,
    set-cmd	 Set-args
  }
}

Reply-op ::= SEQUENCE {
  inv-id	Invocation-ID,
  reply		Value
}

Error-op ::= SEQUENCE {
  inv-id	Invocation-ID,
  error-info	Error-info
}

Reject-op ::= SEQUENCE {
  error-info	Error-info
}

Notify-op ::= SEQUENCE {
  kind		INTEGER,
  arg		Value
}

--
-- Top level message: Abstract Syntax
--
Operation ::= CHOICE {
  call		Call-op,	-- host -> radio
  reply		Reply-op,	-- radio -> host
  error		Error-op,	-- radio -> host
  reject	Reject-op,	-- radio -> host
  notify	Notify-op	-- radio -> host
}

END
